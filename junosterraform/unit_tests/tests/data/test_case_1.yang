module engineer {
    yang-version 1.1;
    namespace "urn:nokia.com:srexperts:types";
    prefix "types";
    revision 2019-05-06;
    typedef age_type {
        description "Engineers start work at 18 and should be retired by 110";
        type int8 {
            range "18 .. 110";
        }
        units years;
    }
    typedef transportation_type {
        description "Method of transportation";
        type enumeration {
            enum foot;
            enum bicycle;
            enum car;
            enum bus;
            enum train;
            enum boat;
            enum aeroplane;
        }
    }
    container configuration {
        container engineer {
            description "Its me";
            leaf name {
                mandatory true;
                type string;
            }
            leaf age {
                type int32;
            }
            leaf commute {
                type string;
            }
            list food {
                key "item_name";
                ordered-by system;
                leaf item_name {
                    type string;
                }
                choice food_type {
                    case office {
                        container coffee {
                            leaf size {
                                type enumeration {
                                    enum tall;
                                    enum grande;
                                    enum venti;
                                }
                            }
                            leaf milk {
                                type boolean;
                            }
                        }
                        leaf donut {
                            type empty;
                        }
                    }
                    case home {
                        leaf salad {
                            type empty;
                        }
                        leaf smoothie {
                            type empty;
                        }
                        leaf coffee {
                            type empty;
                        }
                        // container coffee {
                        //     leaf size {
                        //         type enumeration {
                        //             enum tall;
                        //             enum grande;
                        //             enum venti;
                        //         }
                        //     }
                        //     leaf milk {
                        //         type boolean;
                        //     }
                        // }
                    }
                }
            }
        }
    }
}
